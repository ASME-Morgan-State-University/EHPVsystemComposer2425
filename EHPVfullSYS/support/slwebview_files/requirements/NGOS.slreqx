# NGOS
Need: Our vehicle is for abled body college students between 5'6” and 6’4” ft, with a max weight limit of 300 lbs. 
The ideal geography is in mid-Atlantic urban areas, and it is used for commuting only 10 miles a day via this bike. 
The vehicle will be used for small grocery runs, going to and from class, and going for brief leisure rides.
 It will withstand elements such as rain and snow and have a sporty aspect that is conducive to driving. 
The vehicle will have sensing capabilities to relay the vehicle’s performance to the driver.

## Flexible anthropology of a person (Functional)

### Height Compensation (Functional)
5' - 6' 4"

#### Fit in seat (Functional)

##### Lower Lumbar Support (Functional)

#### Comfortable Handlebars (Functional)

#### Reaching pedals (Functional)

### Weight Compensation (Functional)
<300 lbs

#### Structure is Unable deform under 300 lbs load (Functional)

### Endurance / Strength Compensation (Functional)

#### Pedal Strength Compensation (Functional)
Force needed to do work on the pedals

#### Steering Compensation (Functional)

#### Aerodynamic Drag Mitigation (Functional)

## Built for Urban Destinations (Functional)

### Travel to class (Functional)

#### Be able to secure the vehicle when not in operation (Functional)

#### Sleek Design (Functional)
We dont want to look

#### Comfortably move around people (Functional)
Ability to comfortably move around people

### Small Grocery Runs (Functional)

#### Cargo Compartment (Functional)

#### Secured Cargo (Functional)
Being able to

### Leisure Riding Conditions (Functional)

#### Minimal Effort for Actuaction (Functional)

### Sport Driving Condititions (Functional)
Speeds reach 20+mph

#### Must reach a velocity of 30mph forward (Functional)

#### Acceleration of min 5m/s^2 (Functional)

## Mid-Atlantic Weather/Geography Conditions (Functional)
The goal is to ride in the same conditions as a car.

### Rain (Functional)

### Snow (Functional)

### Heat (Functional)

### Mud (Functional)

### Hills (Functional)

## Enhanced Driver Situational Awareness (Functional)

### Sensors (Functional)

#### Wheel Rotation Speed (Functional)

#### Wattage (Functional)

#### Temperature (Functional)

#### Battery / Voltage level (Functional)

#### Accel/ decel (Functional)

#### Speed (Functional)

#### Sensor Operation Validation (Functional)
The Idea here is to indicate whether or not a sensor is working "in condition" or in other words, providing accurate measurements. (TLDR: Working or faulty)

#### Lane Position Localization (Functional)
Being able to stay in your own lane

### Ergonomic Indicators (Functional)
The ability to see the system diagnostics at a glance

## Safety (Functional)

### Rollover and Fall Protection (Functional)
RO: 90deg+ of falling tilt
Fall: Up to 90 deg of falling tilt

#### Driver immovability (Functional)
When is in a crash, we dont want them to move out of their seat or for their head to experience too much whiplash.

### Electrical Protection (Functional)

#### Emergency Shutoff Capabilities (Functional)

#### Component Preservation (Functional)
Some components may overheat or draw too much current. We need to mitigate that.

### Health Safety (Functional)

#### Preventing Cuts (Functional)

#### Cardiology Safety (Functional)
Want to be mindful of drives heart rate and making sure they dont over exhaust themselves

#### Legal Health Aspects (Functional)

##### Head Safety (Functional)

##### Leg Safety (Functional)

##### Arm Safety (Functional)

#### Driver Ingress and Egress (Functional)

### Road Safety (Functional)

#### Road Visibility (Functional)
To see and be seen
