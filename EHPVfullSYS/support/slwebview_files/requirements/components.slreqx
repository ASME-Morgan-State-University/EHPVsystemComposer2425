# components

## Electronics and Sensing (Container)

### Electrical Connections (Container)

#### Water Proof Wires (Functional)

#### Electrical Terminal Box (Functional)
- Rationale: This component could also be a fuse box

#### Voltage Regulators (Functional)

#### Fuses (Functional)

#### DC Buck Converters (Functional)

### EPS (Functional)
Electrical Power System

#### Physical E-Stop / Breaker Switch (Functional)

#### Software Softstop (Functional)
- Rationale: Potentially, the motor may overheat, and to mitigate that, we can have the software make sure the nominal temp is always good
- Keywords: Software

### Computing (Functional)

### Human Interfaces (Container)

#### Display Screen (Functional)
- Rationale: To see all

#### Voltmeter (Functional)

### Sensors (Functional)

#### IMU (Functional)
Initerial Measurement Unit

#### Encoders (Functional)

#### Lane Position Management System (Functional)

#### Voltmeter (Functional)

#### Ampmeter (Functional)

#### Thermo Couple (Functional)

### Displays (Functional)

### Motor Battery (Functional)

### Aux Battery (Functional)

## Vehicle Dynamics (Container)

### Gear Cassettes (Functional)

### Breaks (Functional)

### Wheel Selection (Functional)

#### Tires (Functional)

#### Rims (Functional)

### Deraillurs (Functional)

### Pedals (Functional)

### Motor (Functional)

### Chain Link (Functional)
Chain link

## Frame and Structures (Container)

### Chassis (Functional)

### RPS (Functional)
Roll over Protection System

### Seating (Functional)

### Steering (Functional)

### Tow Hitch (Functional)

### Harness (Functional)

### RWD Sys (Functional)

#### #50 (Functional)

## Driver (Container)

### Safety (Functional)

#### Heart Rate Monitor (Functional)

#### Helmet (Functional)

### Communications (Functional)

#### Telecommunications / Coms (Functional)
